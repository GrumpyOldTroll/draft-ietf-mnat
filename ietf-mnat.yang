module ietf-mnat {
  yang-version 1.1;

  namespace "urn:ietf:params:xml:ns:yang:ietf-mnat";
  prefix mnat;

  import ietf-yang-types {
    prefix yang;
  }

  import ietf-inet-types {
    prefix inet;
    reference
      "RFC 6991: Common YANG Data Types";
  }

  import ietf-routing-types {
      prefix "rt-types";
      reference "RFC 8294";
  }

  organization
    "IETF MBONED (Multicast Backbone Deployment) Working Group";

  contact
    "WG Web:   <https://datatracker.ietf.org/wg/mboned/>
     WG List:  <mailto:mboned@ietf.org>

     Author:   Jake Holland
               <mailto:jakeholland.net@gmail.com>";

  description
    "Multicast Network Address Translation Model.

     Copyright (c) 2012 - 2020 IETF Trust and the persons
     identified as authors of the code.  All rights reserved.

     Redistribution and use in source and binary forms, with or
     without modification, is permitted pursuant to, and subject
     to the license terms contained in, the Simplified BSD
     License set forth in Section 4.c of the IETF Trust's
     Legal Provisions Relating to IETF Documents
     (https://trustee.ietf.org/license-info).

     This version of this YANG module is part of RFC XXXX; see
     the RFC itself for full legal notices.";

  revision "2020-10-22" {
    description
      "Initial version.";
  }

  grouping multicast-channel {
    choice channel-type {
      description
        "ASM or SSM multicast channels can be represented.";
      case ssm-channel {
        leaf source {
          type inet:ip-address;
          mandatory true;
          description
            "Source address of a multicast channel";
        }
        leaf group {
          type rt-types:ip-multicast-group-address;
          mandatory true;
          description "The global (S,G)'s group address";
        }
      }
      case asm-channel {
        leaf asm-group {
          type rt-types:ip-multicast-group-address;
          mandatory true;
          description "The global (S,G)'s group address";
        }
      }
    }
  }

  typedef egress-key {
    type string;
    description
      "A key for egress identification.";
  }

  typedef assignment-id {
    type uint32;
    description
      "A type for assignment identifiers.";
  }

  identity assignment-state {
    description
      "Base identity to represent assignment states";
  }

  typedef assignment-state {
    type identityref {
      base assignment-state;
    }
    description "Status of an assigned (S,G).";
  }

  identity unassigned {
    base assignment-state;
    description
      "Represents an unassigned global (S,G) that cannot be
       received in the local network.";
  }

  identity assigned-local-multicast {
    base assignment-state;
    description
      "Represents an assigned global (S,G) that can be
       received in the local network by joining the associated
       local-mapping.";
  }

  container assigned-channels {
    config false;
    description
      "MNAT mappings of global (S,G)s into a local transport.";

    list mapped-sg {
      key "id";
      description
        "The local network's assignment of global channels to
         local transport characteristics.";

      leaf id {
        type assignment-id;
        mandatory true;
        description
          "Identifier for this assignment.";
      }
      leaf state {
        type assignment-state;
        mandatory true;
        description
          "Status of the global (S,G)s that are assigned in the
           local network.";
      }
      container global-subscription {
        description
          "The global channel that's mapped.";
        uses multicast-channel;
      }
      container local-mapping {
        choice mapping-type {
          description
            "The description of how the global channel is
             transported within the local network";

          case local-multicast-mapping {
            description
              "Defines the use of a local multicast (S,G) or
               (*,G).";
            uses multicast-channel;
          }
        }
      }
    }
  }

  rpc get-new-egress-key {
    description
      "Obtain a secret key unique to an individual mnat-egress
       instance, assigned by the server and used for subscription
       management.";
    output {
      leaf egress-id {
        type egress-key;
        mandatory true;
        description
          "Egress identifier for subscription management.";
      }
      leaf refresh-period {
        type uint16;
        default 10;
        description
          "Number of seconds to wait between refresh messages.";
      }
    }
  }
  rpc refresh-egress-key {
    description
      "A secret key unique to an individual mnat-egress instance,
       assigned by the server and used for subscription
       management.";
    input {
      leaf egress-id {
        type egress-key;
        mandatory true;
        description
          "Egress identifier for subscription management.";
      }
    }
  }
  rpc join-global {
    description
      "An mnat-egress instance calls this RPC to register to the
       network an interest in a global (S,G).  Depending on
       popularity and local network decisions, this may result in
       adding and possibly removing an entry in
       assigned-channels/mapped-sg.";
    input {
      leaf egress-id {
        type egress-key;
        mandatory true;
        description
          "Egress identifier.";
      }
      uses multicast-channel;
    }
  }
  rpc leave-global {
    description
      "An mnat-egress instance calls this RPC to register to the
       network an interest in a global (S,G).  Depending on
       popularity and local network decisions, this may result in
       adding and possibly removing an entry in
       assigned-channels/mapped-sg.";
    input {
      leaf egress-id {
        type egress-key;
        mandatory true;
        description
          "Egress identifier.";
      }
      uses multicast-channel;
    }
  }
}
